-- message.asn

MY-MODULE DEFINITIONS AUTOMATIC TAGS ::= BEGIN
IdentifierType ::= INTEGER (-32768..32767) -- 16 bits
Message ::= SEQUENCE {
    msgId           IdentifierType,
    myflag           INTEGER (1..255),        -- constrained range
    value           REAL,                    -- floating-point
    szDescription   OCTET STRING (SIZE(10))  -- 10 octets
}
END
